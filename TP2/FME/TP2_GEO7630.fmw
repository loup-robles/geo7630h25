FME workspace TP2_GEO7630.fmw

Parameters:
- SourceDataset_SHAPEFILE_9 = https://donnees.montreal.ca/dataset/dbdfbdba-0725-470d-a23e-da69dbedc4e6/resource/ed333be1-bce6-4890-b0de-9788d5ca0774/download/ilots-de-chaleur-images-satellite-2023.zip   # Source Esri Shapefile(s)
- SourceDataset_SHAPEFILE_7 = $(FME_MF_DIR)Donnees\Segments_routiers\Segments_routiers.shp   # Source Esri Shapefile(s)
- DestDataset_POSTGIS = BD_geo7630h25   # Connection
- SourceDataset_CSV2_14 = https://s3.ca-central-1.amazonaws.com/cdn.bixi.com/wp-content/uploads/2025/01/DonneesOuvertes2024_010203040506070809101112.zip   # Source CSV (Comma Separated Value) File(s)
- SourceDataset_SHAPEFILE_11 = C:\Users\kg291979\Downloads\OneDrive_1_3-16-2025_new\OneDrive_1_3-16-2025_new\shapefile_lab2)bus_metro\shape_counte.shp   # Source Esri Shapefile(s)
- SourceDataset_SHAPEFILE_5 = C:\Users\kg291979\Downloads\OneDrive_1_3-16-2025_new\OneDrive_1_3-16-2025_new\station\station.shp   # Source Esri Shapefile(s)
- SourceDataset_GEOJSON_5 = https://donnees.montreal.ca/dataset/5ea29f40-1b5b-4f34-85b3-7c67088ff536/resource/0dc6612a-be66-406b-b2d9-59c9e1c65ebf/download/reseau_cyclable.geojson   # Source GeoJSON File or URL
- SourceDataset_GEOJSON = https://donnees.montreal.ca/dataset/984f7a68-ab34-4092-9204-4bdfcca767c5/resource/9d3d60d8-4e7f-493e-8d6a-dcd040319d8d/download/geobase.json   # Source GeoJSON File or URL

Readers:
- SHAPEFILE_2: SHAPEFILE from $(SourceDataset_SHAPEFILE_9)
- SHAPEFILE_3: SHAPEFILE from $(SourceDataset_SHAPEFILE_7)
- CSV2_8: CSV2 from $(SourceDataset_CSV2_14)
- SHAPEFILE_6: SHAPEFILE from $(SourceDataset_SHAPEFILE_11)
- SHAPEFILE_4: SHAPEFILE from $(SourceDataset_SHAPEFILE_5)
- GEOJSON_1: GEOJSON from $(SourceDataset_GEOJSON)
- GEOJSON_2: GEOJSON from $(SourceDataset_GEOJSON_5)

Writers:
- POSTGIS_1: POSTGIS to $(DestDataset_POSTGIS)

Bookmark: Stationnements
station (reader SHAPEFILE_4)
    attributes: sNoPlace varchar(254), sNoPlace_X double, sNoPlace_Y double, nLongitude double, nLatitude double, nPositionC double, nPositio_1 double, sStatut long, sGenre varchar(254), sType varchar(254), sAutreTete varchar(254), sAutreTe_1 double, sAutreTe_2 double, sNomRue varchar(254), nSupVelo long, sTypeExplo varchar(254), nTarifHora long, sLocalisat varchar(254), nTarifMax varchar(254)
    -> Reprojector_7

Bookmark: Stationnement
Note: Données shp créée à partir du fichier cvs et transformée sur ArcGIS.
Note: Reprojeter les données
Reprojector_7
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> SpatialFilter [Candidate]
    REPROJECTED -> SpatialFilter_3 [Candidate]
    REPROJECTED -> SpatialFilter_5 [Candidate]
    REPROJECTED -> SpatialFilter_6 [Candidate]
    REPROJECTED -> SpatialFilter_2 [Candidate]
    REPROJECTED -> TP2_Stationnements (writer POSTGIS_1)
TP2_Stationnements (writer POSTGIS_1)
    attributes: snoplace varchar(254), snoplace_x float8, snoplace_y float8, nlongitude float8, nlatitude float8, npositionc float8, npositio_1 float8, sstatut int4, sgenre varchar(254), stype varchar(254), sautretete varchar(254), sautrete_1 float8, sautrete_2 float8, snomrue varchar(254), nsupvelo int4, stypeexplo varchar(254), ntarifhora int4, slocalisat varchar(254), ntarifmax varchar(254)

Bookmark: Réseau cyclable
reseau_cyclable (reader GEOJSON_2)
    attributes: ID_CYCL int, ID_TRC int, AFFICHEUR_DYNAMIQUE string, AVANCEMENT_CODE string, AVANCEMENT_DESC string, COMPTEUR_CYLISTE string, LONGUEUR int, NBR_VOIE int, NOM_ARR_VILLE_CODE string, NOM_ARR_VILLE_DESC string, PROTEGE_4S string, REV_AVANCEMENT_CODE string, REV_AVANCEMENT_DESC string, ROUTE_VERTE string, SAISONS4 string, SAS_VELO string, SEPARATEUR_CODE string, SEPARATEUR_DESC string, TYPE_VOIE_CODE string, TYPE_VOIE_DESC string, TYPE_VOIE2_CODE string, TYPE_VOIE2_DESC string, VILLE_MTL string
    -> Reprojector_2

Bookmark: Stationnements à proximité d'un réseau cyclable protégé
Note: Données GeoJSON importé depuis le site des données ouvertes de la Ville de Montréal
Note: Reprojeter en EPSG : 3857
Reprojector_2
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> AttributeFilter_6
Note: Filtrer pour ne conserver que les pistes cyclables protégées
AttributeFilter_6
    ATTR_NAME = PROTEGE_4S
    ATTR_VALUES = <Empty>,<Missing>,<Null>,<Unfiltered>,Oui
    Oui -> Bufferer
Note: Créer une zone tampon de 20 mètres autour des pistes cyclables pour s'assurer que les points représentants le stationnement soient dans l'emprise de ce buffer.
Bufferer
    ANGLE = 22.5
    CAP_STYLE_LOOKUP = CAP_ARC
    CORNER_STYLE_LOOKUP = JOIN_ARC
    MODE = AREA
    OFFSET = 20
    OFFSET_UNITS = NONE
    PRECISION = APPROX
    CAP_STYLE = Arc
    CORNER_STYLE = Arc
    BUFFERED -> SpatialFilter_2 [Filter]
Note: Jointure spatiale entre les stationnements et le réseau cyclable
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager_8
Note: Créer un champ "indice_pistes_cyclables" et attribuer un score de 0.125 à toutes les entité. / Supprimer les champs inutiles suite à la jointure
AttributeManager_8
    ATTR_TABLE:
      REMOVE AFFICHEUR_DYNAMIQUE (buffer)
      REMOVE AVANCEMENT_CODE (buffer)
      REMOVE AVANCEMENT_DESC (buffer)
      REMOVE COMPTEUR_CYLISTE (buffer)
      REMOVE LONGUEUR (int64)
      REMOVE NBR_VOIE (int64)
      REMOVE NOM_ARR_VILLE_CODE (buffer)
      REMOVE NOM_ARR_VILLE_DESC (buffer)
      REMOVE REV_AVANCEMENT_CODE (buffer)
      REMOVE REV_AVANCEMENT_DESC (buffer)
      REMOVE ROUTE_VERTE (buffer)
      REMOVE SAISONS4 (buffer)
      REMOVE SAS_VELO (buffer)
      REMOVE SEPARATEUR_CODE (buffer)
      REMOVE SEPARATEUR_DESC (buffer)
      REMOVE TYPE_VOIE_CODE (buffer)
      REMOVE TYPE_VOIE_DESC (buffer)
      REMOVE TYPE_VOIE2_CODE (buffer)
      REMOVE TYPE_VOIE2_DESC (buffer)
      REMOVE VILLE_MTL (buffer)
      REMOVE nPositionC (real64)
      REMOVE nPositio_1 (real64)
      REMOVE sStatut (int32)
      REMOVE sGenre (varchar(254))
      REMOVE sType (varchar(254))
      REMOVE sAutreTete (varchar(254))
      REMOVE sAutreTe_1 (real64)
      REMOVE sAutreTe_2 (real64)
      REMOVE sNomRue (varchar(254))
      REMOVE nSupVelo (int32)
      REMOVE sTypeExplo (varchar(254))
      REMOVE nTarifHora (int32)
      REMOVE sLocalisat (varchar(254))
      REMOVE nTarifMax (varchar(254))
      REMOVE _predicate (buffer)
      SET_TO Indice_pistes_cyclable (varchar(15)) = @Evaluate(.125)
    USER_EXPOSED_ATTRIBUTES = Indice_pistes_cyclable
    -> TP2_Stationnements/pistes_cyclables_protegees (writer POSTGIS_1)
Note: Importer dans la base de données PostGIS
TP2_Stationnements/pistes_cyclables_protegees (writer POSTGIS_1)
    attributes: id_cycl int8, id_trc int8, protege_4s varchar, snoplace varchar(254), snoplace_x float8, snoplace_y float8, nlongitude float8, nlatitude float8, indice_pistes_cyclable varchar(15)

Bookmark: ICU
ilots-de-chaleur-images-satellite-2023 (reader SHAPEFILE_2)
    attributes: Temp_Class double, Shape_Area double, Shape_Leng double, Legende varchar(254)
    -> Reprojector_9

Bookmark: Stationnements dans Ilots de chaleur urbain
Note: Données SHP importeé depuis le site des données ouvertes de la Ville de Montréal
Note: Reprojeter en EPSG : 3857
Reprojector_9
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> AttributeFilter_2
Note: Conserver uniquement les entités classifié en "Ilots de chaleur"
AttributeFilter_2
    ATTR_NAME = Temp_Class
    ATTR_VALUES = <Empty>,<Missing>,<Null>,<Unfiltered>,5
    5 -> Dissolver
Note: La données représente plusieurs polygone mais n'est constituée que d'une seule entité. Il faut la désagréger pour que chaque polygone représente une entité
Dissolver
    ACCUM_INPUT_ATTRS = Use Attributes From One Feature
    CLEANING_TOLERANCE_LOOKUP = AUTO
    CONNECT_Z_MODE_LOOKUP = FIRST_WINS
    DEAGGREGATE_INPUT = Yes
    CLEANING_TOLERANCE = Automatic
    CONNECT_Z_MODE = First Wins
    AREA -> SpatialFilter_3 [Filter]
Note: Jointure spatiale entre les stationnements et les Ilots de chaleur
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager_7
Note: Créer un champ "indice_ICU" et attribuer un score de 0.125 à toutes les entité. / Supprimer les champs inutiles suite à la jointure
AttributeManager_7
    ATTR_TABLE:
      REMOVE Shape_Area (real64)
      REMOVE Shape_Leng (real64)
      REMOVE Legende (varchar(254))
      REMOVE nPositionC (real64)
      REMOVE nPositio_1 (real64)
      REMOVE sStatut (int32)
      REMOVE sGenre (varchar(254))
      REMOVE sType (varchar(254))
      REMOVE sAutreTete (varchar(254))
      REMOVE sAutreTe_1 (real64)
      REMOVE sAutreTe_2 (real64)
      REMOVE sNomRue (varchar(254))
      REMOVE nSupVelo (int32)
      REMOVE sTypeExplo (varchar(254))
      REMOVE nTarifHora (int32)
      REMOVE sLocalisat (varchar(254))
      REMOVE nTarifMax (varchar(254))
      SET_TO Indice_ICU (varchar(15)) = @Evaluate(.125)
    USER_EXPOSED_ATTRIBUTES = Indice_ICU
    -> TP2_Stationnements/ICU (writer POSTGIS_1)
Note: Importer dans la base de données PostGIS
TP2_Stationnements/ICU (writer POSTGIS_1)
    attributes: temp_class float8, snoplace varchar(254), snoplace_x float8, snoplace_y float8, nlongitude float8, nlatitude float8, _predicate varchar, indice_icu varchar(15)

Bookmark: Historiques déplacements BIXI 2024
CSV (reader CSV2_8)
    attributes: STARTSTATIONNAME varchar(67), STARTSTATIONARRONDISSEMENT varchar(43), STARTSTATIONLATITUDE real64, STARTSTATIONLONGITUDE real64, ENDSTATIONNAME varchar(67), ENDSTATIONARRONDISSEMENT varchar(43), ENDSTATIONLATITUDE real64, ENDSTATIONLONGITUDE real64, STARTTIMEMS uint64, ENDTIMEMS uint64
    -> VertexCreator_2

Bookmark: Stationnements proches de stations BIXI importantes
Note: Donnée CSV importée depuis le site des données ouvertes de BIXI
Note: Créer des points à partir des champs long/lat de la table
VertexCreator_2
    COORDSYS = EPSG:4326
    MEASURE_TYPE_LOOKUP = CONTINUOUS
    MODE = REPLACE
    REMOVE_ATTRIBUTES = No
    XVAL = @Value(STARTSTATIONLONGITUDE)
    YVAL = @Value(STARTSTATIONLATITUDE)
    MEASURE_TYPE = Continuous
    MODE_NAME = Replace with Point
    -> Reprojector_4
    <REJECTED> -> VertexCreator_2__Rejected_
Note: Reprojeter les données en EPSG: 3857
Reprojector_4
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> StatisticsCalculator_2
    REPROJECTED -> Reprojector_4_Reprojected
Note: Calculer le nombre de départs par station pour l'année 2024
StatisticsCalculator_2
    ATTR_ACCUM_MODE = None
    CALCULATION_MODE = NUMERIC
    FEAT_STATS = STARTSTATIONLONGITUDE,NUMERIC_MODE,,,COUNT,,,,,,,,,,
    GROUP_BY = STARTSTATIONNAME
    SUMMARY -> StatisticsCalculator_2_Summary
    COMPLETE -> DuplicateFilter_2
    COMPLETE -> StatisticsCalculator_2_Complete
Note: Filtrer la couche pour avoir une seule fois les stations dans la table
DuplicateFilter_2
    INPUT_ORDERED_CHOICE_LOOKUP = NO
    KEYATTR = STARTSTATIONNAME
    INPUT_ORDERED_CHOICE = No
    UNIQUE -> AttributeFilter
    UNIQUE -> DuplicateFilter_2_Unique
    DUPLICATE -> DuplicateFilter_2_Duplicate
Note: Filtrer la données pour supprimer les points qui n'ont pas de coordonnées
AttributeFilter
    ATTR_NAME = STARTSTATIONLATITUDE
    ATTR_VALUES = <Empty>,<Missing>,<Null>,<Unfiltered>,0
    <UNFILTERED> -> AttributeManager
Note: Supprimer les champs inutils
AttributeManager
    ATTR_TABLE:
      REMOVE ENDSTATIONNAME (varchar(67))
      REMOVE ENDSTATIONARRONDISSEMENT (varchar(43))
      REMOVE ENDSTATIONLATITUDE (real64)
      REMOVE ENDSTATIONLONGITUDE (real64)
      REMOVE STARTTIMEMS (uint64)
      REMOVE ENDTIMEMS (uint64)
      RENAME_SET_VALUE STARTSTATIONLONGITUDE.total_count > Station_count (uint64)
    -> AttributeManager_3
Note: Créer un filtre "Station_seuil" pour filtrer les stations qui ont comptabilisent environ 30 départs par jour (11 000 départs par an)
AttributeManager_3
    ATTR_TABLE = SET_TO Station_seuil (varchar(200)) = FME_CONDITIONAL:DEFAULT_VALUE'_FME_NO_OP_'BOOL_OP;OR;COMPOSITE_TEST;1;TEST @Value(Station_count) > 11000'IMPORTANTE'FME_NUM_CONDITIONS2___
    USER_EXPOSED_ATTRIBUTES = Station_seuil
    -> AttributeFilter_3
Note: Filtrer selon la valeur seuil pour ne conserver que les stations "Importantes"
AttributeFilter_3
    ATTR_NAME = Station_seuil
    ATTR_VALUES = <Empty>,<Missing>,<Null>,<Unfiltered>,IMPORTANTE
    IMPORTANTE -> Bufferer_2
    IMPORTANTE -> TP2_Stations_BIXI_importantes_2024 (writer POSTGIS_1)
Note: Créer une zone tampon autour des stations BIXI "importantes"
Bufferer_2
    ANGLE = 22.5
    CAP_STYLE_LOOKUP = CAP_ARC
    CORNER_STYLE_LOOKUP = JOIN_ARC
    MODE = AREA
    OFFSET = 50
    OFFSET_UNITS = NONE
    PRECISION = APPROX
    CAP_STYLE = Arc
    CORNER_STYLE = Arc
    BUFFERED -> SpatialFilter_5 [Filter]
Note: Faire la jointure spatiale entre les stationnements et les stations BIXI "importantes.
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager_4
    FAILED -> SpatialFilter_5_Failed
Note: Créer un champ "indice_bus" et attribuer un score de 0.125 à toutes les entités. / Supprimer les champs inutiles suite à la jointure
AttributeManager_4
    ATTR_TABLE:
      REMOVE STARTSTATIONNAME (varchar(67))
      REMOVE STARTSTATIONARRONDISSEMENT (varchar(43))
      REMOVE STARTSTATIONLATITUDE (real64)
      REMOVE STARTSTATIONLONGITUDE (real64)
      REMOVE Station_count (uint64)
      REMOVE sNoPlace_X (real64)
      REMOVE sNoPlace_Y (real64)
      REMOVE nPositionC (real64)
      REMOVE nPositio_1 (real64)
      REMOVE sStatut (int32)
      REMOVE sGenre (varchar(254))
      REMOVE sType (varchar(254))
      REMOVE sAutreTete (varchar(254))
      REMOVE sAutreTe_1 (real64)
      REMOVE sAutreTe_2 (real64)
      REMOVE sNomRue (varchar(254))
      REMOVE nSupVelo (int32)
      REMOVE sTypeExplo (varchar(254))
      REMOVE nTarifHora (int32)
      REMOVE sLocalisat (varchar(254))
      REMOVE nTarifMax (varchar(254))
      REMOVE _predicate (buffer)
      SET_TO Indice_BIXI (varchar(15)) = @Evaluate(.125)
    USER_EXPOSED_ATTRIBUTES = Indice_BIXI
    -> TP2_Stationnements/BIXI (writer POSTGIS_1)
Note: Importer dans la base de données PostGIS
TP2_Stationnements/BIXI (writer POSTGIS_1)
    attributes: station_seuil varchar(200), snoplace varchar(254), nlongitude float8, nlatitude float8, indice_bixi varchar(15)
SpatialFilter_5_Failed: Logger
    LOG_FEATURE = LOG_ONLY
    MAXCOORDS = 20
    MAXFEATS = 20
    MESSAGE = Feature is:
    SEVERITY = INFO
TP2_Stations_BIXI_importantes_2024 (writer POSTGIS_1)
    attributes: startstationname varchar(67), startstationarrondissement varchar(43), startstationlatitude float8, startstationlongitude float8, station_count numeric(20,0), station_seuil varchar(200)
DuplicateFilter_2_Unique: Logger
    LOG_FEATURE = LOG_ONLY
    MAXCOORDS = 20
    MAXFEATS = 20
    MESSAGE = Feature is:
    SEVERITY = INFO
DuplicateFilter_2_Duplicate: Logger
    LOG_FEATURE = LOG_ONLY
    MAXCOORDS = 20
    MAXFEATS = 20
    MESSAGE = Feature is:
    SEVERITY = INFO
StatisticsCalculator_2_Summary: Logger
    LOG_FEATURE = LOG_ONLY
    MAXCOORDS = 20
    MAXFEATS = 20
    MESSAGE = Feature is:
    SEVERITY = INFO
StatisticsCalculator_2_Complete: Logger
    LOG_FEATURE = LOG_ONLY
    MAXCOORDS = 20
    MAXFEATS = 20
    MESSAGE = Feature is:
    SEVERITY = INFO
Reprojector_4_Reprojected: Logger
    LOG_FEATURE = LOG_ONLY
    MAXCOORDS = 20
    MAXFEATS = 20
    MESSAGE = Feature is:
    SEVERITY = INFO
VertexCreator_2__Rejected_: Logger
    LOG_FEATURE = LOG_ONLY
    MAXCOORDS = 20
    MAXFEATS = 20
    MESSAGE = Feature is:
    SEVERITY = INFO

Bookmark: Geobase
geobase_mtl (reader GEOJSON_1)
    attributes: ID_TRC int, DEB_GCH int, FIN_GCH int, ARR_GCH string, SENS_CIR int, CLASSE int, LIE_VOIE string, TYP_VOIE string, DIR_VOIE string, NOM_VOIE string, DEB_DRT int, FIN_DRT int, ARR_DRT string, LIM_GCH string, LIM_DRT string, POSITION int, ODONYME string
    -> Reprojector

Bookmark: Stationnements sur routes principales
Note: Donnée GeoJSON importée depuis le site des données ouvertes de la Ville de Montréal
Note: Reprojeter en EPSG : 3857
Reprojector
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> AttributeFilter_4
Note: Filtrer la données pour conserver les artères primcipales dont le code de classe est égale à 7
AttributeFilter_4
    ATTR_NAME = CLASSE
    ATTR_VALUES = <Empty>,<Missing>,<Null>,<Unfiltered>,7
    7 -> Bufferer_4
Note: Créer une zone tampon de 20 mètres autour des routes pour s'assurer que les points représentants le stationnement soient dans l'emprise de ce buffer.
Bufferer_4
    ANGLE = 22.5
    CAP_STYLE_LOOKUP = CAP_ARC
    CORNER_STYLE_LOOKUP = JOIN_ARC
    MODE = AREA
    OFFSET = 20
    OFFSET_UNITS = NONE
    PRECISION = APPROX
    CAP_STYLE = Arc
    CORNER_STYLE = Arc
    BUFFERED -> SpatialFilter_6 [Filter]
Note: Faire la jointure spatiale entre les stationnements et les routes principales
SpatialFilter_6
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager_6
Note: Créer un champ "indice_routes_principales" et attribuer un score de 0.125 à toutes les entité. / Supprimer les champs inutiles suite à la jointure
AttributeManager_6
    ATTR_TABLE:
      REMOVE DEB_GCH (int64)
      REMOVE FIN_GCH (int64)
      REMOVE ARR_GCH (buffer)
      REMOVE SENS_CIR (int64)
      REMOVE LIE_VOIE (buffer)
      REMOVE TYP_VOIE (buffer)
      REMOVE DIR_VOIE (buffer)
      REMOVE NOM_VOIE (buffer)
      REMOVE DEB_DRT (int64)
      REMOVE FIN_DRT (int64)
      REMOVE ARR_DRT (buffer)
      REMOVE LIM_GCH (buffer)
      REMOVE LIM_DRT (buffer)
      REMOVE POSITION (int64)
      REMOVE ODONYME (buffer)
      REMOVE nPositionC (real64)
      REMOVE nPositio_1 (real64)
      REMOVE sStatut (int32)
      REMOVE sGenre (varchar(254))
      REMOVE sType (varchar(254))
      REMOVE sAutreTete (varchar(254))
      REMOVE sAutreTe_1 (real64)
      REMOVE sAutreTe_2 (real64)
      REMOVE sNomRue (varchar(254))
      REMOVE nSupVelo (int32)
      REMOVE sTypeExplo (varchar(254))
      REMOVE nTarifHora (int32)
      REMOVE sLocalisat (varchar(254))
      REMOVE nTarifMax (varchar(254))
      REMOVE _predicate (buffer)
      SET_TO Indice_route_principale (varchar(13)) = @Evaluate(.5)
    USER_EXPOSED_ATTRIBUTES = Indice_route_principale
    -> TP2_Stationnements/Routes_principales (writer POSTGIS_1)
Note: Importer dans la base de données PostGIS
TP2_Stationnements/Routes_principales (writer POSTGIS_1)
    attributes: id_trc int8, classe int8, snoplace varchar(254), snoplace_x float8, snoplace_y float8, nlongitude float8, nlatitude float8, indice_route_principale varchar(13)

Bookmark: Arrets de bus/métro
shape_counte (reader SHAPEFILE_6)
    attributes: stop_code long, stop_id varchar(80), stop_name varchar(80), stop_url varchar(80), wheelchair long, route_id varchar(80), loc_type long, shelter double, service_id varchar(80), COUNTER_rt number(18,0)
    -> Reprojector_6

Bookmark: Stationnements proches de bus à forte connectivité
Note: Donnée créée avec le code Python. Ajout d'un "Counter" sur le fichier des stations de bu pour pouvoir compter combien de lignes passent à chaque arrêt. Puis transformation en shp
Note: Reprojeter en ESPG : 3857
Reprojector_6
    DEST = EPSG:3857
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> AttributeManager_2
Note: Créer un champ "faible/fort" et attribuer la valeur selon une condition. Si un arret de bus acceuille moins de 3 lignes différentes alors elle a une faible connectivité au reste du réseau. Si elle acceuille plus de 3 lignes, alors elle a une forte connectivité au réseau.
AttributeManager_2
    ATTR_TABLE = SET_TO station_fort_faible (varchar(200)) = FME_CONDITIONAL:DEFAULT_VALUE'FAIBLE'BOOL_OP;OR;COMPOSITE_TEST;1;TEST @Value(COUNTER_rt) > 3'FORTE'FME_NUM_CONDITIONS2___
    USER_EXPOSED_ATTRIBUTES = station_fort_faible
    -> AttributeFilter_5
Note: Sélectionner uniquement les stations qui ont une forte connectivité au réseau
AttributeFilter_5
    ATTR_NAME = station_fort_faible
    ATTR_VALUES = <Empty>,<Missing>,<Null>,<Unfiltered>,FORTE
    FORTE -> Bufferer_3
Note: Faire une zone tempon de 150m autour des arrets de bus sélectionné
Bufferer_3
    ANGLE = 22.5
    CAP_STYLE_LOOKUP = CAP_ARC
    CORNER_STYLE_LOOKUP = JOIN_ARC
    MODE = AREA
    OFFSET = 150
    OFFSET_UNITS = METERS
    PRECISION = APPROX
    CAP_STYLE = Arc
    CORNER_STYLE = Arc
    BUFFERED -> SpatialFilter [Filter]
Note: Filtrer les stationnements qui ne sont pas dans une zone de forte connectivité au réseau de transport en commun
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager_5
Note: Créer un champ "indice_bus" et attribuer un score de 0.125 à toutes les entité. / Supprimer les champs inutiles suite à la jointure
AttributeManager_5
    ATTR_TABLE:
      REMOVE stop_url (varchar(80))
      REMOVE wheelchair (int32)
      REMOVE loc_type (int32)
      REMOVE shelter (real64)
      REMOVE service_id (varchar(80))
      REMOVE nPositionC (real64)
      REMOVE nPositio_1 (real64)
      REMOVE sStatut (int32)
      REMOVE sGenre (varchar(254))
      REMOVE sType (varchar(254))
      REMOVE sAutreTete (varchar(254))
      REMOVE sAutreTe_1 (real64)
      REMOVE sAutreTe_2 (real64)
      REMOVE sNomRue (varchar(254))
      REMOVE nSupVelo (int32)
      REMOVE sTypeExplo (varchar(254))
      REMOVE nTarifHora (int32)
      REMOVE sLocalisat (varchar(254))
      REMOVE _predicate (buffer)
      SET_TO Indice_bus (varchar(15)) = @Evaluate(.125)
    USER_EXPOSED_ATTRIBUTES = Indice_bus
    -> TP2_Stationnements/bus (writer POSTGIS_1)
Note: Importer dans la base de données PostGIS
TP2_Stationnements/bus (writer POSTGIS_1)
    attributes: stop_code int4, stop_id varchar(80), stop_name varchar(80), route_id varchar(80), counter_rt int8, station_fort_faible varchar(200), snoplace varchar(254), snoplace_x float8, snoplace_y float8, nlongitude float8, nlatitude float8, ntarifmax varchar(254), indice_bus varchar(15)
