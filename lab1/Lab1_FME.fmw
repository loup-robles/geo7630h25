FME workspace Lab1_FME.fmw

Parameters:
- DestDataset_POSTGIS = BD_GEO7630H25   # Connection
- SourceDataset_CSV2_5 = https://donnees.montreal.ca/dataset/c1d65779-d3cb-44e8-af0a-b9f2c5f7766d/resource/28a4957d-732e-48f9-8adb-0624867d9bb0/download/businesses.csv   # Source CSV (Comma Separated Value) File(s)
- SourceDataset_CSV2 = https://donnees.montreal.ca/dataset/c1d65779-d3cb-44e8-af0a-b9f2c5f7766d/resource/28a4957d-732e-48f9-8adb-0624867d9bb0/download/businesses.csv   # Source CSV (Comma Separated Value) File(s)

Readers:
- CSV2_1: CSV2 from $(SourceDataset_CSV2) in EPSG:32188
- CSV2_2: CSV2 from $(SourceDataset_CSV2_5)

Writers:
- POSTGIS_1: POSTGIS to $(DestDataset_POSTGIS)

CSV (reader CSV2_2)
    attributes: business_id uint32, name varchar(80), address varchar(48), city varchar(21), state varchar(15), type varchar(57), statut varchar(30), date_statut uint32, latitude y_coordinate, longitude x_coordinate, x real64, y real64
    -> VertexCreator
CODEMS_TABLE_1 (writer POSTGIS_1)
    attributes: business_id int8, name varchar(80), address varchar(48), city varchar(21), state varchar(15), type varchar(57), statut varchar(30), date_statut int8, latitude float8, longitude float8, x float8, y float8

Bookmark: New Bookmark
VertexCreator
    COORDSYS = EPSG:4326
    MEASURE_TYPE_LOOKUP = CONTINUOUS
    MODE = REPLACE
    REMOVE_ATTRIBUTES = No
    XVAL = @Value(longitude)
    YVAL = @Value(latitude)
    MEASURE_TYPE = Continuous
    MODE_NAME = Replace with Point
    -> CODEMS_TABLE_1 (writer POSTGIS_1)
    <REJECTED> -> VertexCreator__Rejected_
VertexCreator__Rejected_: Logger
    LOG_FEATURE = LOG_ONLY
    MAXCOORDS = 20
    MAXFEATS = 20
    MESSAGE = Feature is:
    SEVERITY = INFO
