FME workspace lab3.fmw

Parameters:
- SourceDataset_CSV2_3 = https://donnees.montreal.ca/dataset/b89fd27d-4b49-461b-8e54-fa2b34a628c4/resource/64e28fe6-ef37-437a-972d-d1d3f1f7d891/download/arbres-publics.csv   # Source CSV (Comma Separated Value) File(s)
- DestDataset_POSTGIS = BD_GEO7630H25   # Connection
- SourceDataset_GEOJSON = https://donnees.montreal.ca/dataset/2e9e4d2f-173a-4c3d-a5e3-565d79baa27d/resource/35796624-15df-4503-a569-797665f8768e/download/espace_vert.json   # Source GeoJSON File or URL

Readers:
- CSV2_2: CSV2 from $(SourceDataset_CSV2_3) in EPSG:32188
- GEOJSON_1: GEOJSON from $(SourceDataset_GEOJSON)

Writers:
- POSTGIS_1: POSTGIS to $(DestDataset_POSTGIS)

CSV (reader CSV2_2)
    attributes: INV_TYPE varchar(1), EMP_NO uint32, ARROND uint32, ARROND_NOM varchar(43), Rue varchar(63), Rue_cote varchar(2), No_civique uint32, Emplacement varchar(23), Sigle varchar(6), Essence_latin varchar(45), Essence_fr varchar(48), Essence_ang varchar(44), DHP real32, Date_Releve datetime, Date_Plantation datetime, LOCALISATION varchar(49), Localisation_code varchar(5), CODE_PARC varchar(8), NOM_PARC varchar(60), Rue_de varchar(53), Rue_a varchar(53), Distance_pave real32, Distance_ligne_rue varchar(14), Stationnement_jour varchar(4), Stationnement_heure varchar(11), District uint32, Arbre_remarquable varchar(1), Code_secteur uint32, Nom_secteur varchar(23), Coord_X x_coordinate,
      Coord_Y y_coordinate, Longitude real64, Latitude real64
    -> Filtre_longitude
Reprojector
    DEST = EPSG:32188
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> PointOnAreaOverlayer [POINT]
espvert.esv_espace_vert_vue_datefin_null (reader GEOJSON_1)
    attributes: OBJECTID string, Type string, Lien string, Nom string, NUM_INDEX string, SUPERFICIE string, PROPRIETE string, GESTION string, COMPETENCE string, TYPO1 string, TYPO2 string
    -> Reprojector_2
Reprojector_2
    DEST = EPSG:32188
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> PointOnAreaOverlayer [AREA]
PointOnAreaOverlayer
    ATTR_ACCUM_MODE = Merge Incoming
    ATTR_CONFLICT_RES_LOOKUP = ORIGINAL_IF_CONFLICT
    DEAGGREGATE_INPUT = Yes
    OV_ATTR = tree_count
    POLYS_FIRST = NO
    ATTR_CONFLICT_RES = Use Original
    AREA -> AttributeKeeper
AttributeKeeper
    CREATE_BULK_MODE_FEATURES = NO
    KEEP_ATTRS = NOM_PARC,SUPERFICIE,tree_count
    -> AttributeManager
AttributeManager
    ATTR_TABLE = SET_TO tree_density (real64) = @Evaluate(@Value(tree_count)/@Area())
    USER_EXPOSED_ATTRIBUTES = tree_density
densite_arbres_quartiers (writer POSTGIS_1)

Bookmark: Filtrer les poitns en dehors de l'agglomération montréalaise
Filtre_longitude: AttributeRangeFilter
    IN_ATTR = Longitude
    LUT = -73.99,-73.0,-73.99 .. -73.0
    -73.99 .. -73.0 -> Filtre_latitude
    <UNFILTERED> -> Logger
Filtre_latitude: AttributeRangeFilter
    IN_ATTR = Latitude
    LUT = 45.4,45.8,45.4 .. 45.8
    45.4 .. 45.8 -> Reprojector
    <UNFILTERED> -> Logger_2
Logger_2
    LOG_FEATURE = LOG_ONLY
    MAXCOORDS = 20
    MAXFEATS = 20
    MESSAGE = Feature is:
    SEVERITY = INFO
Logger
    LOG_FEATURE = LOG_ONLY
    MAXCOORDS = 20
    MAXFEATS = 20
    MESSAGE = Feature is:
    SEVERITY = INFO
